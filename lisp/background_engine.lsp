(vl-load-com)
(defun GNI:REP (s old new / p) (if (and s old new (/= old "")) (progn (while (setq p (vl-string-search (strcase old) (strcase s))) (setq s (strcat (substr s 1 p) new (substr s (+ p (strlen old) 1))))) s) s))
(defun GNI:MAP (s / p) (foreach p GNI:MAPS (if (and (listp p) (car p) (cadr p)) (setq s (GNI:REP s (car p) (cadr p))))) s)
(defun GNI:UPD (e / d a o n r) (if (and e (setq d (entget e)) (setq a (assoc 1 d))) (progn (setq o (cdr a) n (GNI:MAP o)) (if (/= o n) (progn (setq r (entmod (subst (cons 1 n) a d))) (if r (progn (entupd e) T) nil)) nil)) nil))
(defun GNI:MARK (p mode u c / f) (setq f (open p "w")) (if f (progn (princ (strcat "MODE=" mode "\nUPDATED=" (itoa u) "\nENTITIES=" (itoa c) "\n") f) (close f) T) nil))
(defun GNI:PROCESS (mode / ss i e u c q m) (setq u 0 c 0) (princ "\nGNI_STAGE:SELECT_ENTITIES") (setq ss (ssget "_X" '((-4 . "<OR") (0 . "TEXT") (0 . "MTEXT") (0 . "ATTRIB") (0 . "ATTDEF") (-4 . "OR>") (410 . "Model")))) (if ss (progn (setq i 0) (repeat (sslength ss) (setq e (ssname ss i) i (1+ i) c (1+ c)) (if (GNI:UPD e) (setq u (1+ u)))))) (princ (strcat "\nGNI_STAGE:ENTITY_UPDATE_DONE:UPDATED=" (itoa u) ":ENTITIES=" (itoa c))) (princ "\nGNI_STAGE:QSAVE") (setq q (vl-catch-all-apply 'command-s (list "_.QSAVE"))) (if (vl-catch-all-error-p q) (princ (strcat "\nGNI_STAGE_ERROR:QSAVE:" (vl-catch-all-error-message q))) (progn (princ "\nGNI_STAGE:QSAVE_DONE") (setq m (strcat (getvar "DWGPREFIX") (getvar "DWGNAME") ".gni.txt")) (if (GNI:MARK m mode u c) (princ (strcat "\nGNI_MIGRATION_OK:" (getvar "DWGNAME") ":UPDATED=" (itoa u) ":ENTITIES=" (itoa c))) (princ "\nGNI_MIGRATION_ERROR:MARKER_WRITE_FAILED")))) (princ))
(princ "\nGNI_BACKGROUND_ENGINE_0_3A_LOADED")
(princ "\nGNI_BACKGROUND_ENGINE_0_3A_7_QSAVE")
(princ)
